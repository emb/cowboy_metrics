-- Copyright (c) 2013-2015, Ed Mohmaed Barwani <ed.barwani@gmail.com>
-- All rights reserved.
--
-- Redistribution and use in source and binary forms, with or without
-- modification, are permitted provided that the following conditions are
-- met:
--
-- 1. Redistributions of source code must retain the above copyright
-- notice, this list of conditions and the following disclaimer.
--
-- 2. Redistributions in binary form must reproduce the above copyright
-- notice, this list of conditions and the following disclaimer in the
-- documentation and/or other materials provided with the distribution.
--
-- THIS SOFTWARE IS PROVIDED BY THE COPYRIGHT HOLDERS AND CONTRIBUTORS
-- "AS IS" AND ANY EXPRESS OR IMPLIED WARRANTIES, INCLUDING, BUT NOT
-- LIMITED TO, THE IMPLIED WARRANTIES OF MERCHANTABILITY AND FITNESS FOR
-- A PARTICULAR PURPOSE ARE DISCLAIMED. IN NO EVENT SHALL THE COPYRIGHT
-- HOLDER OR CONTRIBUTORS BE LIABLE FOR ANY DIRECT, INDIRECT, INCIDENTAL,
-- SPECIAL, EXEMPLARY, OR CONSEQUENTIAL DAMAGES (INCLUDING, BUT NOT
-- LIMITED TO, PROCUREMENT OF SUBSTITUTE GOODS OR SERVICES; LOSS OF USE,
-- DATA, OR PROFITS; OR BUSINESS INTERRUPTION) HOWEVER CAUSED AND ON ANY
-- THEORY OF LIABILITY, WHETHER IN CONTRACT, STRICT LIABILITY, OR TORT
-- (INCLUDING NEGLIGENCE OR OTHERWISE) ARISING IN ANY WAY OUT OF THE USE
-- OF THIS SOFTWARE, EVEN IF ADVISED OF THE POSSIBILITY OF SUCH DAMAGE.

COWBOY-MIB DEFINITIONS ::= BEGIN

IMPORTS
    MODULE-IDENTITY, OBJECT-TYPE,
    Counter32
        FROM SNMPv2-SMI
    DisplayString
        FROM SNMPv2-TC
    MODULE-COMPLIANCE, OBJECT-GROUP
        FROM SNMPv2-CONF
    otpModules, otpApplications
        FROM OTP-REG
    ;

otpModule MODULE-IDENTITY
    LAST-UPDATED "2013122311500Z"
    ORGANIZATION "Undefined"
    CONTACT-INFO
        "Contact:  Your support team!"
    DESCRIPTION
        "This MIB is used for monitoring Erlag Cowboy HTTP server."

    REVISION     "2013122311500Z"
    DESCRIPTION
        "Initial revision"

    ::= { otpModules 100 } -- Picked a value of my hat.

-- Deine the general structure of the OID.

cowboyMIB        OBJECT IDENTIFIER ::= { otpApplications 100 } -- Picked another value :-)
cowboyMIBConformance
                 OBJECT IDENTIFIER ::= { cowboyMIB 1 }
cowboyMIBObjects OBJECT IDENTIFIER ::= { cowboyMIB 2 }

-- Here we may have request/responses etc, we might as well split them.
request          OBJECT IDENTIFIER ::= { cowboyMIBObjects 1}
response         OBJECT IDENTIFIER ::= { cowboyMIBObjects 2}

totalRequests OBJECT-TYPE
    SYNTAX      Counter32
    MAX-ACCESS  read-only
    STATUS      current
    DESCRIPTION
        "Total number of incoming requests."
    ::= { request 1 }

requestTable OBJECT-TYPE
    SYNTAX      SEQUENCE OF RequestEntry
    MAX-ACCESS  not-accessible
    STATUS      current
    DESCRIPTION
        "Describe requests in table for each http method"
    ::= { request 2 }

requestEntry OBJECT-TYPE
    SYNTAX      RequestEntry
    MAX-ACCESS  not-accessible
    STATUS      current
    DESCRIPTION
        "A row showing each http method stats."
    INDEX       { requestMethod }
    ::= { requestTable 1 }

RequestEntry ::= SEQUENCE {
    requestMethod      DisplayString,
    requestMethodCount Counter32
}

requestMethod OBJECT-TYPE
    SYNTAX      DisplayString
    MAX-ACCESS  not-accessible
    STATUS      current
    DESCRIPTION
        "HTTP Method, e.g. GET, POST.. etc"
    ::= { requestEntry 1 }

requestMethodCount OBJECT-TYPE
    SYNTAX      Counter32
    MAX-ACCESS  read-only
    STATUS      current
    DESCRIPTION
        "The total number of requests  associated with HTTP
        Method"
    DEFVAL     { 0 }
    ::= { requestEntry 2 }

totalResponses OBJECT-TYPE
    SYNTAX      Counter32
    MAX-ACCESS  read-only
    STATUS      current
    DESCRIPTION
        "Total number of outgoing responses."
    ::= { response 1 }

totalResponseSize OBJECT-TYPE
    SYNTAX      Counter32
    UNITS       "bytes"
    MAX-ACCESS  read-only
    STATUS      current
    DESCRIPTION
        "Total body size of outgoing responses."
    ::= { response 2 }

responseTable OBJECT-TYPE
    SYNTAX      SEQUENCE OF ResponseEntry
    MAX-ACCESS  not-accessible
    STATUS      current
    DESCRIPTION
        "Describe responses entry table."
    ::= { response 3 }

responseEntry OBJECT-TYPE
    SYNTAX      ResponseEntry
    MAX-ACCESS  not-accessible
    STATUS      current
    DESCRIPTION
        "A response row showing StatusCode and available stats."
    INDEX       { responseCode }
    ::= { responseTable 1 }

ResponseEntry ::= SEQUENCE {
    responseCode      DisplayString,
    responseCodeCount Counter32,
    responseCodeSize  Counter32
}

responseCode OBJECT-TYPE
    SYNTAX      DisplayString
    MAX-ACCESS  not-accessible
    STATUS      current
    DESCRIPTION
        "HTTP Response Status Code."
    ::= { responseEntry 1 }

responseCodeCount OBJECT-TYPE
    SYNTAX      Counter32
    MAX-ACCESS  read-only
    STATUS      current
    DESCRIPTION
        "The number of responses corresponding to status code class."
    ::= { responseEntry 2 }

responseCodeSize OBJECT-TYPE
    SYNTAX     Counter32
    UNITS      "bytes"
    MAX-ACCESS read-only
    STATUS     current
    DESCRIPTION
        "The response body size per status code class."
    ::= { responseEntry 3 }


-- Required Compliance Group

cowboyMIBCompliances
                OBJECT IDENTIFIER ::= { cowboyMIBConformance 1 }
cowboyMIBGroups OBJECT IDENTIFIER ::= { cowboyMIBConformance 2 }

cowboyBasicCompilance MODULE-COMPLIANCE
    STATUS      current
    DESCRIPTION
        "Compliance statement for SNMPv2 entities."
    MODULE
        MANDATORY-GROUPS { cowboyRequestGroup,
                           cowboyResponseGroup
                         }
    ::= { cowboyMIBCompliances 1 }

cowboyRequestGroup OBJECT-GROUP
    OBJECTS { totalRequests,
              requestMethodCount
            }
    STATUS    current
    DESCRIPTION
        "Cowboy Request instrumentation group."
    ::= { cowboyMIBGroups 1}

cowboyResponseGroup OBJECT-GROUP
    OBJECTS { totalResponses,
              totalResponseSize,
              responseCodeCount,
              responseCodeSize
            }
    STATUS    current
    DESCRIPTION
        "Cowboy Response instrumentatation group."
    ::= { cowboyMIBGroups 2}


END
